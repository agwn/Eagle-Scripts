#usage "<b>Extract board info, text and info for all tagged components for making a library footprint to use the module on a PCB<\b>.\n"
        "Usage: RUN exp-module-fp.ulp"
        "<author>Author: agwn</author>"

// Definitions:

real    GridDist = 50.0;
enum    {unitINCH, unitMIL, unitMM, unitMIC};
string  h, cmd = "";
int     unit = unitMIL;   // predefined unit, can be changed to unitMM, unitINCH, unitMIC
int     show_script = 1;
int     Result;
string  Status = "";


int exp_Dimension = 1;
int exp_tPlace = 1;
int exp_bPlace = 1;
int exp_tDocu = 0;
int exp_bDocu = 0;
int exp_Holes = 1;

// in Eagle 5, oneMil should be 100
// in Eagle 6, the resolution increased by 32, so oneMil should be 3200
int oneMil = 3200;
if ( EAGLE_VERSION < 6 ) { oneMil = 100; }
//int oneMil = 100; // 1mil EAGLE stores all size values as int values with a resolution of 1/320000mm (0.003125µ).
// flags for layer information to be exported
int outlineWidth = 8;

// Statements:

// get project path, if in board or schematic, otherwise library path
string get_project_path()
{
  string s = "", p = "";
  if (library)  { library(L)  s = L.name;}
  if (board)    { board(B)     s = B.name;}
  if (schematic){ schematic(S) s = S.name;}
  char c = '/';
  int pos = strrchr(s, c);
  if (pos >= 0) {
    p = strsub(s, 0, pos + 1);
  }
  return p;
}

string add_comment(string s) {
  string c = "";
  sprintf(c, "# %s\n",s);
  
  return c;
}

string add_command(string s) {
  string c = "";
  sprintf(c, "%s\n",s);
  
  return c;
}

real u2unit(int u)
{
  if (unit == unitMIL)
    return u2mil(u);
  if (unit == unitMM)
    return u2mm(u);
  if (unit == unitINCH)
    return u2inch(u);
  if (unit == unitMIC)
    return u2mic(u);
}

string getPadShape(int s)
{
  if (s == PAD_SHAPE_SQUARE)
    return "Square";
  if (s == PAD_SHAPE_ROUND)
    return "Round";
  if (s == PAD_SHAPE_OCTAGON)
    return "Octagon";
  if (s == PAD_SHAPE_LONG)
    return "Long";
  if (s == PAD_SHAPE_OFFSET)
    return "Offset";
}

real snap(int n) // returns next grid point
{
  return round(u2unit(n) / GridDist)   * GridDist;
}

int n = 0, x[], y[], l[], UsedLayers[];

int isNew(int X, int Y, int L) {
  for (int i = 0; i < n; i++) {
    if (x[i] == X && y[i] == Y && (l[i] == L || l[i] == LAYER_VIAS ))
      return 0;
  }
  return 1;
}

void Move(int Layer)
{
  if (UsedLayers[Layer]) {
    h = ""; sprintf(h, "DISPLAY NONE %d;\n", Layer); cmd += h;
    // Snap the signal wires and vias:
    for (int i = 0; i < n; i++) {
      if (l[i] == Layer && (u2unit(x[i]) != snap(x[i]) || u2unit(y[i]) != snap(y[i]))) {
        h = ""; sprintf(h, "MOVE (%f %f) (%f %f);\n", u2unit(x[i]), u2unit(y[i]), snap(x[i]), snap(y[i])); cmd += h;
      }
    }
  }
}


void export_brd_outline (void)
{
  cmd += add_comment("BEGIN: export of board outline");
  // TODO: get the curves right, remove diagonal hack
  if (exp_Dimension) {
    board(B) {
      //cmd += "SET WIRE_BEND 6\n";
      // set wire bend to straight lines HACK!
      cmd += "SET WIRE_BEND 2\n";

      // TODO: extract arcs 

      if (exp_tPlace) {
        cmd += add_comment("START: board outline top");
        B.wires(W) {
          if (W.layer == LAYER_DIMENSION) {
            h = "";
            sprintf(h, "CHANGE LAYER %d\nCHANGE WIDTH %3.2f\n",
                LAYER_TPLACE, u2unit(outlineWidth*oneMil));
            cmd += h;
            if (W.arc) {
              h = "";
              //sprintf(h, "ARC CCW (%3.3f %3.3f) (%3.3f %3.3f) (%3.3f %3.3f)\n",
              //    u2unit(W.arc.x1), u2unit(W.arc.y1), u2unit(W.arc.x2), u2unit(W.arc.y2), u2unit(W.arc.xc), u2unit(W.arc.yc));
              sprintf(h, "WIRE (%3.3f %3.3f) @+%3.3f (%3.3f %3.3f)\n",
                  u2unit(W.arc.x1), u2unit(W.arc.y1), u2unit(W.arc.radius), u2unit(W.arc.x2), u2unit(W.arc.y2));
              //cmd += add_comment(h);
              cmd += h;
            } else {
              h = "";
              sprintf(h, "WIRE (%3.3f %3.3f) (%3.3f %3.3f)\n",
                  u2unit(W.x1), u2unit(W.y1), u2unit(W.x2), u2unit(W.y2));
              cmd += h;
            }
          }
        }
        cmd += add_comment("END: board outline top");
      }

      if (exp_bPlace) {
        cmd += add_comment("START: board outline bottom");
        B.wires(W) {
          if (W.layer == LAYER_DIMENSION) {
            h = "";
            sprintf(h, "CHANGE LAYER %d\nCHANGE WIDTH %3.2f\n",
                LAYER_BPLACE, u2unit(outlineWidth*oneMil));
            cmd += h;
            if (W.arc) {
              h = "";
              //sprintf(h, "ARC CCW (%3.3f %3.3f) (%3.3f %3.3f) (%3.3f %3.3f)\n",
              //    u2unit(W.arc.x1), u2unit(W.arc.y1), u2unit(W.arc.x2), u2unit(W.arc.y2), u2unit(W.arc.xc), u2unit(W.arc.yc));
              sprintf(h, "WIRE (%3.3f %3.3f) @+%3.3f (%3.3f %3.3f)\n",
                  u2unit(W.arc.x1), u2unit(W.arc.y1), u2unit(W.arc.radius), u2unit(W.arc.x2), u2unit(W.arc.y2));
              //cmd += add_comment(h);
              cmd += h;
            } else {
              h = "";
              sprintf(h, "WIRE (%3.3f %3.3f) (%3.3f %3.3f)\n",
                  u2unit(W.x1), u2unit(W.y1), u2unit(W.x2), u2unit(W.y2));
              cmd += h;
            }
          }
        }
        cmd += add_comment("END: brd outline bottom");
      }
    }
  }
  cmd += add_comment("END: export of board outline\n");
}



void export_brd_labels(void)
{
  cmd += add_comment("BEGIN: export of labels");
  board(B) {
    B.texts(T) {
      // labeling on the standard (Place) layers
      if ((exp_tPlace && (T.layer == LAYER_TPLACE)) || (exp_bPlace && (T.layer == LAYER_BPLACE))) {
        h = "";
        sprintf(h, "CHANGE LAYER %d\nCHANGE SIZE %3.2f\n",
            T.layer, u2unit(T.size));
        cmd += h;
        h = "";
        if (T.layer == LAYER_BPLACE) { // mirror the text for bottom layer
          sprintf(h, "TEXT '%s' MR%2.1f (%3.3f %3.3f)\n",
              T.value, T.angle, u2unit(T.x), u2unit(T.y));
        } else {
          sprintf(h, "TEXT '%s' R%2.1f (%3.3f %3.3f)\n",
              T.value, T.angle, u2unit(T.x), u2unit(T.y));
        }
        cmd += h;
      }

      // labeling on the documentation layers
      if ((exp_tDocu && (T.layer == LAYER_TDOCU)) || (exp_bDocu && (T.layer == LAYER_BDOCU))) {
        h = "";
        sprintf(h, "CHANGE LAYER %d\nCHANGE SIZE %3.2f\n",
            T.layer, u2unit(T.size));
        cmd += h;
        h = "";
        if (T.layer == LAYER_BDOCU) { // mirror the text for bottom layer
          sprintf(h, "TEXT '%s' MR%2.1f (%3.3f %3.3f)\n",
              T.value, T.angle, u2unit(T.x), u2unit(T.y));
        } else {
          sprintf(h, "TEXT '%s' R%2.1f (%3.3f %3.3f)\n",
              T.value, T.angle, u2unit(T.x), u2unit(T.y));
        }
        cmd += h;
      }
    }

    // set wire bend to straight lines
    cmd += "SET WIRE_BEND 2\n";
    B.wires(W) {
      // labeling using wires
      if ((exp_tPlace && (W.layer == LAYER_TPLACE)) || (exp_bPlace && (W.layer == LAYER_BPLACE))) {
        h = "";
        sprintf(h, "CHANGE LAYER %d\nCHANGE WIDTH %3.2f\n",
            W.layer, u2unit(W.width));
        cmd += h;

        h = "";
        sprintf(h, "WIRE (%3.3f %3.3f) (%3.3f %3.3f)\n",
            u2unit(W.x1), u2unit(W.y1), u2unit(W.x2), u2unit(W.y2));
        cmd += h;
      }
    }
  }
  cmd += add_comment("END: export of labels\n");
}



void export_brd_components(void)
{
  cmd += add_comment("BEGIN: export of components");
  board(B) {
    B.elements(E) {
      // can sperate out these later if wanted
      if ((E.attribute["EXP2MODFP"]) || (E.attribute["EXP2MODMECMNT"])) {
        // extract all through hole contacts 
        E.package.contacts(C) {
          if (C.pad) {
            h = "";
            sprintf(h, "CHANGE DRILL %f\nPAD %f %s R%3.2f '%s$%s' (%3.3f %3.3f)\n",
                u2unit(C.pad.drill),
                u2unit(C.pad.diameter[LAYER_TOP]), getPadShape(C.pad.shape[LAYER_TOP]),
                C.pad.angle, E.name, C.name, u2unit(C.pad.x), u2unit(C.pad.y));
            cmd += h;
          }
        }
        E.package.holes(H) {
          // drill holes
            h = "";
            sprintf(h, "HOLE %f (%3.3f %3.3f)",
                u2unit(H.drill), u2unit(H.x), u2unit(H.y));
            cmd += h;
        }
        E.package.circles(C) {
          // draw circle
          h = "";
          sprintf(h, "CHANGE LAYER %d\nCIRCLE %f (%f %f) (%f %f)\n",
              C.layer, u2unit(C.width),
              u2unit(C.x), u2unit(C.y), u2unit(C.x + C.radius), u2unit(C.y));
          cmd += h;
        }
        E.package.rectangles(R) {
          // draw rectangles
          h = "";
          sprintf(h, "CHANGE LAYER %d\nRECT R%f (%f %f) (%f %f)\n",
              R.layer, u2unit(R.angle),
              u2unit(R.x1), u2unit(R.y1), u2unit(R.x2), u2unit(R.y2));
          cmd += h;
        }
        E.package.polygons(P) {
          // draw polygons
        }
      }
    }
  }
  cmd += add_comment("END: export of components\n");
}


void export_brd_holes(void)
{
  cmd += add_comment("BEGIN: export of other drill holes");
  if (exp_Holes) {
    board(B) {
      B.holes(H) {
        h = "";
        sprintf(h, "CHANGE DRILL %f\nHOLE (%3.3f %3.3f)\n",
            u2unit(H.drill), u2unit(H.x), u2unit(H.y));
        cmd += h;
      }
    }
  }
  cmd += add_comment("END: export of other drill holes\n");
}


void Export_to_File (void)
{
  cmd += add_comment("config");
  // set import units to be the same as the export units
  if (unit == unitMIL)
    cmd += "GRID MIL\n";
  if (unit == unitMM)
    cmd += "GRID MM\n";
  if (unit == unitINCH)
    cmd += "GRID INCH\n";
  if (unit == unitMIC)
    cmd += "GRID MIC\n";
  cmd += "\n";
  
  board(B) {
    // Remember the active layers:
    int ActiveLayers[];
    B.layers(L) {
      ActiveLayers[L.number] = L.visible;
    }

    // Export board outline
    export_brd_outline();

    // Export board labels (text and wires) 
    export_brd_labels();

    // Export all tagged connectors/headers
    export_brd_components();

    // Export all drill holes (holes placed seperate from any component)
    export_brd_holes();
  }

  cmd += add_comment("cleanup");
  cmd += "GRID LAST\n";
}



//---- main ----------------------------------------------------------------------

string fileName;

if (!board) {
  dlgMessageBox(usage + "<hr><b>ERROR: No board!</b><p>\nThis program can only work in the board editor.");
  exit(1);
}

Result = dlgDialog("Export Module Footprint") {
  dlgHBoxLayout {
    dlgStretch(1);
    dlgLabel("Export this PCB as a module footprint");
    dlgStretch(1);
  }
  dlgSpacing(10);
  dlgHBoxLayout {
    dlgLabel("Note: Electrical footprint always included. Other layers optional.");
  }
  dlgSpacing(10);
  dlgGroup("Additional layers (other than Pads) to include") {
    dlgGridLayout  {
      dlgCell(0, 0, 0, 1) dlgCheckBox("Dimension", exp_Dimension);
      dlgCell(1, 0) dlgCheckBox("tPlace", exp_tPlace);
      dlgCell(1, 1) dlgCheckBox("bPlace", exp_bPlace);
      dlgCell(2, 0) dlgCheckBox("tDocu", exp_tDocu);
      dlgCell(2, 1) dlgCheckBox("bDocu", exp_bDocu);
      dlgCell(3, 0, 3, 1) dlgCheckBox("Holes", exp_Holes);
    }
  }
  dlgSpacing(10);
  dlgHBoxLayout {
    dlgLabel("File &name:");
    dlgStringEdit(fileName);
    dlgPushButton("Bro&wse") {
      fileName = dlgFileSave("Select a file", fileName);
    }
  }
  dlgSpacing(10);
  dlgHBoxLayout {
    dlgSpacing(10);
    dlgVBoxLayout {
      dlgStretch(1);
      dlgLabel(Status, 1);
      dlgHBoxLayout {
        dlgPushButton("+&Export")   {
          Status = "Busy..."; dlgRedisplay();
          Export_to_File();
          if (fileName) {
            if (fileName != "") output(fileName, "wt") {printf(cmd);}
          } else {
            string dest = dlgFileSave("Save Script File", get_project_path()+"module_fp.scr", "*.scr");
            if (dest != "") output(dest, "wt") {printf(cmd);}
          }
          dlgAccept(0);
        }
        dlgPushButton("-&Cancel") exit(0);
      }
      dlgSpacing(10);
    }
  }
};

if (Result) exit(Result);

if (show_script) {
  Result = dlgDialog("Shows Exported Data") {
    dlgVBoxLayout {
      dlgLabel("Shows Exported Data");
      dlgTextView(cmd);
    }
    dlgHBoxLayout {
      dlgPushButton("+OK") dlgAccept(0);
    }
  };
}

if (!Result) exit(0);
//exit(cmd);
